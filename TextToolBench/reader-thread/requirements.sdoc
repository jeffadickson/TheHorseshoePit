[DOCUMENT]
TITLE: GNU grep reader-thread experiment requirements

[REQUIREMENT]
UID: READAHEAD-001
TITLE: Preserve the matcher and source provenance
STATEMENT: >>>
Integrate a C++20 bounded reader pipeline into GNU grep 3.0 without replacing its matcher. Compare with the original source build used in the existing benchmark. Preserve the official archive identity, compiler flags, patch and executable hashes.
<<<
COMMENT: grep.patch; build.sh; results/environment.json; results/compiler.txt; README.rst. User-requested experiment; no upstream or general compatibility claim.

[REQUIREMENT]
UID: READAHEAD-002
TITLE: Preserve input bytes and observable search output
STATEMENT: >>>
The adapter shall deliver input bytes in order without duplication or loss. Check empty files, unterminated and long lines, binary bytes, multiple files, stdin fallback, line counts and selected-line output. Verify every timed output length, SHA-256 and exit status against an independent ASCII oracle.
<<<
COMMENT: read-ahead.cpp Reader::read; native-check.cpp property; Experiment.cs Oracle and Validate; results/validation.json; results/runs.jsonl. Finite checks establish tested behavior only.

[REQUIREMENT]
UID: READAHEAD-003
TITLE: Coordinate cancellation, errors and seeks
STATEMENT: >>>
Join the reader before grep finalizes or closes the descriptor. Restore the consumed-byte offset rather than the prefetched offset. Coordinate seeks by discarding pending buffers. Propagate EOF and read errors; retain synchronous behavior for stdin and unsupported descriptors. Test early exits and malformed inputs with timeouts.
<<<
COMMENT: read-ahead.cpp read_ahead_end and read_ahead_seek; grep.patch; native-check.cpp property and negative_cases; Experiment.cs Validate; results/native-check.log. Allocation/thread creation failure, interrupted system calls and exceptional library failures remain incompletely exercised.

[REQUIREMENT]
UID: READAHEAD-004
TITLE: Bound buffering and retain the original path
STATEMENT: >>>
Use at most the configured slot count, with 3 slots of 256 KiB by default. Accept chunk sizes from 4096 through 8388608 bytes and slot counts from 1 through 16. Enable explicitly using GREP_READ_AHEAD=1. Invalid settings or unavailable resources shall fall back to the original reader.
<<<
COMMENT: read-ahead.cpp setting and read_ahead_begin; native-check.cpp negative_cases; Experiment.cs Validate. Bounds are inferred implementation choices for this experiment, not independent user acceptance criteria.

[REQUIREMENT]
UID: READAHEAD-005
TITLE: Reproducible measurement and verification evidence
STATEMENT: >>>
Reuse the original 32 MiB corpus and retain its exact size and hash. Run original, adapter-disabled and three queue sizes sequentially in seeded shuffled order, with two warmups and fifteen measured runs per cell. Record raw wall and CPU time, medians and quartiles. Collect source coverage, sanitizer, libFuzzer, negative and mutation evidence, and disclose scope limitations and background workload interference.
<<<
COMMENT: Experiment.cs Main; native-verify.sh; results/summary.csv; results/environment.json; results/gcov.log; results/fuzz.log; results/mutations.csv; results/stryker. Warm-cache Windows/MSYS2 measurement only; no cold-storage or CPU-cache-residency conclusion.

[REQUIREMENT]
UID: READAHEAD-006
TITLE: Explicit vector byte comparisons
STATEMENT: >>>
Provide opt-in AVX2 first-match searches for one or two unsigned byte values, including equal needles, unaligned input and scalar tails. Never load beyond the supplied byte count. Retain original library behavior when GREP_VECTOR_SEARCH is disabled. Connect the helpers to GNU grep's driver and kwset searches without changing regex or matching-line semantics.
<<<
COMMENT: vector-search.cpp; vector-search.h; build.sh; vector-check.cpp; native-check.cpp; results/optimized/native. Test reference cases, guard pages, fuzz inputs, scalar fallback and deliberately faulty source variants. Whole release binaries target this processor; the helper fallback does not make them portable.

[REQUIREMENT]
UID: READAHEAD-007
TITLE: Reduce queue overhead while preserving slot ownership
STATEMENT: >>>
Allocate overwrite-only queue buffers, exposing only published initialized bytes. Allow copying without holding the queue mutex while keeping the slot unavailable to the producer until the copy completes. Preserve bounded backpressure, early shutdown, errors and offsets. Replace variable-modulo index updates with bounded increment-and-reset.
<<<
COMMENT: read-ahead.cpp Reader::produce, Reader::read and Reader constructor; native-check.cpp; native-verify.sh ASan/UBSan, Memcheck and fault-injection checks. Optimization choices are inferred implementation details.

[REQUIREMENT]
UID: READAHEAD-008
TITLE: Separate diagnostic profiling from timing
STATEMENT: >>>
Build an O3/native/vectorized profiling executable that records read, copy, lock, queue-full, queue-empty and shutdown wall intervals, byte/call counts, queue high-water mark and per-thread CPU clocks when supported. Emit diagnostics only after joining the producer. Validate profiled output and byte/queue invariants. Keep all profiling code absent from timing builds and retain raw records for three repetitions of each task with vector search both disabled and enabled.
<<<
COMMENT: queue-profile.h; read-ahead.cpp; build.sh; Experiment.cs --profile; results/profile. Overlapping thread wall intervals are not additive CPU shares. Unsupported CPU clocks remain JSON null. Instrumented timings are diagnostic only; no instruction-sampling or hardware-counter claim.

[REQUIREMENT]
UID: READAHEAD-009
TITLE: Contemporaneous optimization comparison
STATEMENT: >>>
Reuse the exact previous corpus. Interleave original grep, the preserved previous queue executable, optimized queue with library searches, vector search without the queue, and optimized queue with vector search. Use O3, loop/SLP vectorization and native processor targeting; retain two warmups, fifteen measured rounds, exact source/tool/executable provenance and independent output validation. Preserve earlier timing evidence separately.
<<<
COMMENT: build.sh; Experiment.cs; results/optimized; results/profile; README.rst. Warm-cache process-inclusive timings on a shared Windows host; finite experiments do not establish universal gains.

[REQUIREMENT]
UID: READAHEAD-010
TITLE: Compare 256-byte AVX2 search blocks
STATEMENT: >>>
Implement a compile-time 256-byte search variant using eight 32-byte comparisons and a combined rejection mask. On a match, preserve first-byte ordering across all lanes. Retain 32-byte and scalar tails without reading beyond the supplied region. Compare preserved 32-byte and new 256-byte binaries on the original corpus with and without the queue, using independent output validation, two warmups and fifteen measured rounds. Additionally measure both kernels interleaved in one process with file loading excluded from timing. Record executable code size, flags, coverage and finite verification evidence without claiming universal speedup.
<<<
COMMENT: vector-search.cpp GREP_VECTOR_BLOCK; vector-check.cpp; vector-kernel.cpp; build-block256.sh; verify-block256.sh; Experiment.cs --block256; results/block256. The 256 bytes denote input handled per loop, not hardware vector width or code size. Runtime CPU portability remains outside the native-build contract.

[REQUIREMENT]
UID: READAHEAD-011
TITLE: Isolate queue copy instruction choices
STATEMENT: >>>
Compare the existing library memcpy with explicit cached AVX2 copying and rep movsb in separate O3/native/vectorized binaries. Retain identical 32-byte search objects, queue settings, input corpus and output semantics. Copy only nonoverlapping initialized regions without alignment requirements or access beyond the supplied count. Preserve the current memcpy default. Record interleaved end-to-end timings, separate diagnostic profiles, and copy/consume kernel timings. Verify byte content, boundary sentinels, protected pages, negative settings, randomized fuzz inputs and deliberate mutations; report coverage and tooling limitations.
<<<
COMMENT: memory-copy.cpp and memory-copy.h; read-ahead.cpp Reader::read; copy-check.cpp; copy-kernel.cpp; build-copy.sh; verify-copy.sh; Experiment.cs --copy; Run-Experiment.ps1 Copy modes; results/copy; COPY.rst. Copy variants are processor-specific experiments, not replacements for overlap-safe memmove or portable runtime libraries. No cold-storage or hardware-counter claim.
